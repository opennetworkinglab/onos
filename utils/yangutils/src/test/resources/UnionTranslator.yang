module Test {
    yang-version 1;
    namespace http://huawei.com;
    prefix Ant;
    container valid {
        leaf invalid-interval {
            type union {
                type int32;
                type int8;
            }
        }
    }
}
