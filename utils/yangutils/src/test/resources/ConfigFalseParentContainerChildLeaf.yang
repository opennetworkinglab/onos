module Test {
    yang-version 1;
    namespace http://huawei.com;
    prefix Ant;
    container valid {
        config false;
        leaf invalid-interval {
            type "uint16";
            units "seconds";
            status current;
            config true;
            reference "RFC 6020";
        }
    }
}
