module Test {
    yang-version 1;
    namespace http://huawei.com;
    prefix Ant;
    leaf speed {
        type enumeration {
            enum 10m;
            enum 100m;
            enum 10m {
                value 11;
            }
        }
    }
}
