module Test {
yang-version 1;
namespace urn:ietf:params:xml:ns:yang:ietf-ospf;
prefix On;
import ietf {
prefix On2;
revision-date 2015-02-03;
}
import itut {
prefix On3;
revision-date 2016-02-03;
}
contact "Test";
}
