module Test {
    yang-version 1;
    namespace http://example.com/schema/ds0;
    prefix On;

    import interface-module {
        prefix "if";
    }
    import ietf-yang-types {
             prefix "P";
         }
    augment "/if:interfaces/if:ifEntry" {
        leaf ds0ChannelNumber {
            type P:ChannelNumber;
        }
    }
}
