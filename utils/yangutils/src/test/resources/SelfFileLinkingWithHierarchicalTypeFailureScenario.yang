module Test {
    yang-version 1;
    namespace http://huawei.com;
    prefix Ant;
    typedef Percentage {
    type INT;
    }
    container ospf {
        list valid {
            key "invalid-interval";
            leaf invalid-interval {
                type Ant:FirstClass;
            }
            typedef FirstClass {
                type Ant:PassingClass;
            }
        }
        typedef PassingClass {
            type Percentage;
        }
    }
}
