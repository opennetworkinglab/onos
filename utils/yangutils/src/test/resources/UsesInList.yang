module Test {
    yang-version 1;
    namespace http://huawei.com;
    prefix Ant;
    import ietf-yang-types {
             prefix "P";
         }
    list valid {
        key address;
        leaf address {
            type P:ip;
        }
        uses endpoint {
            description "grouping under test";
            status current;
            reference "RFC 6020";
        }
    }
}
