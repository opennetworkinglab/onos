module Test {
    yang-version 1;
    namespace http://huawei.com;
    prefix Ant;
    grouping Percentage {
        leaf hello{
            type string;
        }
    }
    container ospf {
        list valid {
            key "invalid";
            leaf invalid{
                type string;
            }
            uses Ant:FirstClass;
            grouping FirstClass {
                uses PassingClass;
            }
        }
        grouping PassingClass {
            uses Ant:Percentage;
        }
    }
}
