module Test {
yang-version 1;
organization "ONOS";
namespace urn:ietf:params:xml:ns:yang:ietf-ospf;
prefix On;
import ietf {
prefix On2;
revision-date 2015-02-03;
}
include itut; {
revision-date 2016-02-03;
}
include sdn {
revision-date 2014-02-03;
}
contact "Test";
}
