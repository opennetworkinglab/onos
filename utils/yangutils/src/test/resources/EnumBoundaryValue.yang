module Test {
    yang-version 1;
    namespace http://huawei.com;
    prefix Ant;
    leaf ifType {
        type enumeration {
             enum "unbounded";
             enum ZERO;
             enum two;
             enum four;
             enum seven {
                 value 21474836472147483647;
             }
         }
     }
}
