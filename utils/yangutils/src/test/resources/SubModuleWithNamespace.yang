submodule Test {
belongs-to ONOS {
prefix On1;
}
yang-version 1;
namespace urn:ietf:params:xml:ns:yang:ietf-ospf;
import ietf {
prefix On2;
revision-date 2015-02-03;
}
include itut {
revision-date 2016-02-03;
}
include sdn {
revision-date 2014-02-03;
}
contact "Test";
organization "ONOS";
}
