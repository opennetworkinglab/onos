module Test {
    yang-version 1;
    namespace http://huawei.com;
    prefix Ant;
    uses treat;
    grouping treat {
        leaf treat{
            type string;
        }
        container test{
            leaf leaf2{
                type string;
            }
        }
    }
}
