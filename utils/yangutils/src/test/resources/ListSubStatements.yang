module Test {
    yang-version 1;
    namespace http://huawei.com;
    prefix Ant;
    list ospf {
        key "process-id";
        config true;
        max-elements 10;
        min-elements 3;
        description "list description";
        status current;
        reference "list reference";
        leaf invalid-interval {
            type "uint16";
            units "seconds";
            status current;
            reference "RFC 6020";
        }
    }
}
