module Test {
    yang-version 1;
    namespace http://huawei.com;
    prefix Ant;
    grouping endpoint {
        leaf address {
            type ip-address;
        }
        leaf port {
            type port-number;
        }
    }
    grouping endpoint {
        leaf address {
            type ip-address;
        }
        leaf port {
            type port-number;
        }
    }
}
