module Test {
    yang-version 1;
    namespace http://huawei.com;
    prefix Ant;
    leaf invalid-interval {
        type string {
            pattern "[a-zA-Z]" {
                description "pattern description";
                reference "pattern reference";
            }
         }
    }
}
