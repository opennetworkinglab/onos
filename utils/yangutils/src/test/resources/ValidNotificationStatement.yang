module rock {
    namespace "http://example.net/rock";
    prefix "rock";

    import ietf-yang-types {
             prefix "P";
         }
    notification link-failure {
        description "A link failure has been detected";
        status deprecated;
        reference "reference";
        typedef my-type {
           status deprecated;
           type int32;
        }
        leaf if-name {
           type string;
        }
        leaf if-admin-status {
           type P:admin-status;
        }
        leaf if-oper-status {
           type P:oper-status;
        }
    }
}
