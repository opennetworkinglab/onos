module Test {
    yang-version 1;
    namespace http://huawei.com;
    prefix Ant;
    leaf invalid-interval {
      type "uint16";
      description "Interval before a " + "route is declared invalid"
    }
}
