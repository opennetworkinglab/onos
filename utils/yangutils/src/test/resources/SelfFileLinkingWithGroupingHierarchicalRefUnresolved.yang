module Test {
    yang-version 1;
    namespace http://huawei.com;
    prefix Ant;
    import ietf-yang-types {
        prefix "P";
    }
    grouping create {
        uses P:valid;
    }
    container test{
        uses create;
    }
}
