module Test {
    yang-version 1;
    namespace http://huawei.com;
    prefix Ant;
    grouping endpoint {
    }
    container valid {
        uses endpoint {
            description "grouping under test";
            status current;
            reference "RFC 6020";
        }
    }
}
