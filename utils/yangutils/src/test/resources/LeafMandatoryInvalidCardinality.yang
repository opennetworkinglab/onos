module Test {
    yang-version 1;
    namespace http://huawei.com;
    prefix Ant;
    leaf invalid-interval {
        type "uint16";
        units "seconds";
        description "Interval before a route is declared invalid";
        config true;
        mandatory true;
        mandatory false;
        status current;
        reference "RFC 6020";
    }
}
