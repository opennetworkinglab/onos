module Test {
    yang-version 1;
    namespace http://huawei.com;
    prefix Ant;
    container ospf {
        list valid {
            key "invalid-interval";
            leaf invalid-interval {
                type hello;
            }
        }
        typedef hello {
            type string;
        }
    }
}
