module Test {
    yang-version 1;
    namespace http://huawei.com;
    prefix Ant;
    list ospf {
        key "process-id";
        container interface {
            leaf invalid-interval {
                type "uint16";
                units "seconds";
                status current;
                reference "RFC 6020";
            }
        }
        leaf process-id {
            type "string";
        }
    }
}
