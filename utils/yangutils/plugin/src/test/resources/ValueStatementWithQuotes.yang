module Test {
    yang-version 1;
    namespace http://huawei.com;
    prefix Ant;
    leaf speed {
        type enumeration {
          enum 10m {
	     value "10";
          }
          enum 100m {
	     value "100";
          }
          enum auto {
	     value "1000";
          }
        }
    }
}
