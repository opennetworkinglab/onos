module Test {
    yang-version 1;
    namespace http://huawei.com;
    prefix Ant;
    list valid {
        key "define";
        leaf define {
            type string;
        }
        container standard {
            typedef node {
                type leafref {
                    path "/invalid-interval";
                }
            }
            container present {
                typedef name {
                    type node;
                }
                leaf interval {
                    type name;
                }
            }
        }
    }
    leaf-list invalid-interval {
        type enumeration {
            enum 10m;
            enum 100m;
            enum auto;
        }
    }
}
