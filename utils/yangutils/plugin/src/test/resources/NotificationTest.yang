module NotificationTest {
    yang-version 1;
    namespace http://huawei.com;
    prefix Ant;
    notification test {
        leaf type {
            type string;
        }
        leaf severity {
            type string;
        }
    }
}
