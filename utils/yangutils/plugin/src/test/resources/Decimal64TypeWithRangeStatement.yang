module Test {
    yang-version 1;
    namespace http://huawei.com;
    prefix Ant;
    leaf validDecimal {
         type decimal64 {
            fraction-digits 8; 
            range "-92233720368.54775808 .. 92233720368.54775807";
         }
    }
}
