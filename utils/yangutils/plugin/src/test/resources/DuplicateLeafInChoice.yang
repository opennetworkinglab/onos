module Test {
    yang-version 1;
    namespace http://huawei.com;
    prefix Ant;
     container food {
       choice snack {
           case sports-arena {
               leaf pretzel {
                   type empty;
               }
               leaf beer {
                   type empty;
               }
           }
           case late-night {
               leaf pretzel {
                   type empty;
               }
           }
    }
}
