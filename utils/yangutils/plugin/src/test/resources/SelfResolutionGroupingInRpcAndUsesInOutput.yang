module rock {
    namespace "http://example.net/rock";
    prefix "rock";

    rpc rock-the-house {
        description "description";
        status current;
        reference "reference";
	grouping hello {
	    list valid {
        	    key invalid-interval;
    	            reference "RFC 6020";
    		    leaf invalid-interval {
        	    type "uint16";
        	    units "seconds";
        	    status current;
        	    reference "RFC 6020";
    		    }
	     }
         }
        input {
             leaf zip-code {
                 type string;
             }
             uses hello;
        }
        output {
             leaf status {
                 type string;
             }
    	     uses hello;
        }
    }
}
