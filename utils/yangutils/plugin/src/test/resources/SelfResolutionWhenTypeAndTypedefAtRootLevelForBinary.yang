module ospf {
     namespace "urn:cisco:params:xml:ns:yang:ospf";
     // replace with IANA namespace when assigned
     prefix ospf;
      revision 2020-10-20 {
       description
         "Initial revision.";
     }

    typedef type14 {
        type binary;
    }

    leaf typedef14 {
       type type14;
     }
}
