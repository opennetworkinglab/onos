module rock {
    namespace "http://example.net/rock";
    prefix "rock";

    rpc activate-software-image {
        description "description";
        input {
            leaf image-name {
                type string;
            }
            list ospf {
                key "invalid-interval";
                config true;
                max-elements 10;
                min-elements 3;
                leaf invalid-interval {
                    type uint16;
                }
            }
            container isis {
               config true;
               leaf invalid-interval {
                   type uint16;
               }
           }
        }
    }
}
