module module1 {
    yang-version 1;
    namespace "http://huawei.com";
    prefix Ant;
    import module2 {
        prefix p;
    }
    leaf invalid-interval {
        type p:hello;
    }
    typedef hello {
        type string;
    }
}
