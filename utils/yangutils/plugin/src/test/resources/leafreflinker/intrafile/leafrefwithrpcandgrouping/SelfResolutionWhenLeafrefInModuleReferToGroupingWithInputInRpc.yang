module SelfResolutionWhenLeafrefInModuleReferToGroupingWithInputInRpc {
    yang-version 1;
    namespace "urn:ietf:params:xml:ns:yang:ietf-network";
    prefix nd;
    rpc networks {
        description
        "Serves as top-level container for a list of networks.";
        grouping input {
            leaf network-id {
                type string;
                description
                "Identifies a network.";
            }
        }
        input {
            leaf network-id {
                type uint8;
                description
                "Identifies a network.";
            }
        }
    }
    leaf network-ref {
        type leafref {
        path "/networks/input/network-id";
        }
    }
}
