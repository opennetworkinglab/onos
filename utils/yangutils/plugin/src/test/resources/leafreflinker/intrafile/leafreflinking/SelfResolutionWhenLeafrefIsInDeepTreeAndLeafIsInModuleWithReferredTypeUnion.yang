module Test {
    yang-version 1;
    namespace http://huawei.com;
    prefix Ant;
    list valid {
        key "define";
        leaf define {
            type string;
        }
        container standard {
            container present {
                leaf name {
                    type leafref {
                        path "/invalid-interval";
                    }
                }
            }
        }
    }
    leaf invalid-interval {
        type union {
            type int32;
            type enumeration {
                enum "unbounded";
            }
        }
    }
}
