module ietf-network {
    yang-version 1;
    namespace "urn:ietf:params:xml:ns:yang:ietf-network";
    prefix nd;
    rpc networks {
        description
        "Serves as top-level container for a list of networks.";
        input {
            leaf-list network-id {
                type uint8;
                description
                "Identifies a network.";
            }
        }
        output {
        }
    }
    leaf-list network-ref {
        type leafref {
        path "/networks/input/network-id";
        }
    }
}
