module Test {
    yang-version 1;
    namespace http://huawei.com;
    prefix Ant;
    typedef invalid-interval {
        type string {
            pattern "[a-zA-Z]";
         }
    }
    leaf xyz {
       type invalid-interval {
           pattern "[a-z]";
       }
    }
}
