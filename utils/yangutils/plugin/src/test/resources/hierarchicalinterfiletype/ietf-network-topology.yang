module ietf-network-topology {
   yang-version 1;
   namespace "urn:ietf:params:xml:ns:yang:ietf-network-topology";
   prefix nt;

   import ietf-inet-types {
     prefix inet;
   }
   import ietf-network {
     prefix nd;
   }
         leaf source-node {
           type nd:node-id;
           description
             "Source node identifier, must be in same topology.";
         }
 }
