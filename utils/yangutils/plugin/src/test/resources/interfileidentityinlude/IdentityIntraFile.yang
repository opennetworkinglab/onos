submodule syslog4 {
     yang-version 1;
     belongs-to "syslog3" {
         prefix "sys3";
     }

     identity tunnel-type {
         description
            "Base identity from which specific tunnel types are derived.";
     }

     identity ref-address-family {
         reference "http://www.iana.org/assignments/address-family-numbers/address-family-numbers.xhtml#address-family-numbers-2";
     }
}
