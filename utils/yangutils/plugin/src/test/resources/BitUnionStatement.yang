module Test {
    yang-version 1;
    namespace http://huawei.com;
    prefix Ant;
    leaf type15 { 
        type union {
            type bits {
                bit disable-nagle {
                    position 0;
                }
                bit auto-sense-speed {
                    position 1;
                }
                bit Mb-only {
                    position 2;
                }
            }
        }
    }
}
