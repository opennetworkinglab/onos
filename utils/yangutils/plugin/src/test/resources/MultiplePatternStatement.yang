module Test {
    yang-version 1;
    namespace http://huawei.com;
    prefix Ant;
    leaf-list invalid-interval {
        type string {
            pattern "[a-zA-Z]";
            pattern "[a-z]";
         }
    }
}
