module Test {
    yang-version 1;
    namespace http://huawei.com;
    prefix Ant;
    container 1valid {
        reference "RFC 6020";
        leaf invalid-interval {
            type "uint16";
            units "seconds";
            status current;
            reference "RFC 6020";
        }
    }
}
