module module2 {
    yang-version 1;
    namespace http://huawei.com;
    prefix Ant2;
    revision 2007-06-09 {
        description "Initial revision.";
    }
    typedef hello {
        type string;
    }
}
