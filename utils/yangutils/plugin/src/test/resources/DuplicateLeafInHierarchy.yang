module Test {
    yang-version 1;
    namespace http://huawei.com;
    prefix Ant;
    container food {
        choice snack {
            case sports-arena {
                leaf pretzel {
                    type empty;
                }
            }
            case late-night {
                choice lunch {
                    case late {
                        leaf pretzel {
                            type empty;
                        }
                    }
                }
            }
        }
    }
}
