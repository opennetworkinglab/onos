module Test {
    yang-version 1;
    namespace http://huawei.com;
    prefix Ant;
    leaf ifType {
        type enumeration {
             enum four{
                 value 7;
             }
             enum seven {
                 value 2147483647;
             }
             enum five {
                 value 5;
             }       
         }
    }
}
