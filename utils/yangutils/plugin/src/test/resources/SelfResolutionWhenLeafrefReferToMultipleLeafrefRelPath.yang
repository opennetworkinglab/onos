module Test {
    yang-version 1;
    namespace http://huawei.com;
    prefix Ant;
    list valid {
        key "define";
        leaf define {
            type string;
        }
        container standard {
            container present {
                leaf-list name {
                    type leafref {
                        path "../../../../transmitter/send";
                    }
                }
            }
        }
    }
    container reference {
        list found {
            key "define";
            leaf define {
                type string;
            }
            container reciever {
                leaf remove {
                    type leafref {
                        path "../../../../valid/standard/present/name";
                    }
                }
            }
        }
    }
    list transmitter {
        key "send";
        leaf send {
            type leafref {
                path "../../invalid-interval";
            }
        }
    }
    leaf-list invalid-interval {
        type enumeration {
            enum 10m;
            enum 100m;
            enum auto;
        }
    }
}
