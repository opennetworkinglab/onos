module Test {
    yang-version 1;
    namespace http://huawei.com;
    prefix Ant;
    container food {
        choice snack {
            list sports-arena {
            }
        }
    }
}
leaf invalid {
