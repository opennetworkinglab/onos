module ietf-sd-onos-service-types {

       namespace "urn:ietf:params:xml:ns:yang:ietf-sd-onos-service-types";  
       prefix service-types ; 

	grouping qos-if-car {  
           description "qos parameter." ;  
         list qos-if-car {  
       	key "direction";  
           description "cars qos policy." ;   
           leaf direction {  
               type enumeration {  
                   enum inbound{  
                       value 0 ;  
                       description "inbound." ;  
                   }  
                   enum outbound {  
                       value 1 ;  
                       description "outbound." ;  
                   }  
               }  
        description "qos for interface car" ;  
           }   
}
}

	container qos-policy {  
          description "The qos policy of the vpn service." ;  
               container qos-if-cars {  
             description "qos policy if car." ;  
                   list qos-if-car {  
                     key "direction";  
                     uses qos-if-car;  
             description "List of qos parameters." ;  
                   }  
               }  
           }  

     rpc close-l3vpn {  
     description "Close l3vpn." ;  
         input {  
             leaf l3vpn-id {  
                 type string;  
           description "vpn id." ;  
             }  
             container ac-status {   
           description "Access status of the vpn." ;  
                 list acs{  
                     key "id";  
             description "Access information." ;  
                     leaf id {  
                         type string;  
               description "Access id." ;  
                     }  
                     leaf admin-status {  
                         type string;  
               description "Administration status." ;  
                     }                      
                 }
             }  
         }  
     }    
}
