module Test {
    yang-version 1;
    namespace http://huawei.com;
    prefix Ant;
    container valid {
        presence "invalid";
        leaf invalid-interval {
            type "uint16";
            units "seconds";
            status current;
            reference "RFC 6020";
        }
    }
}
