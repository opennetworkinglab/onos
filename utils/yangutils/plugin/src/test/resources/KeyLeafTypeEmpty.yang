module Test {
    yang-version 1;
    namespace http://huawei.com;
    prefix Ant;
    list valid {
        key "invalid-interval";
        leaf invalid-interval {
            type "empty";
            units "seconds";
            status current;
            reference "RFC 6020";
        }
    }
}
