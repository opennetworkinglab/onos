module Test {
    yang-version 1;
    namespace http://huawei.com;
    prefix Ant;
     container food {
       choice snack {
           case sports-arena {
               leaf pretzel {
                   type empty;
               }
               leaf beer {
                   type empty;
               }
           }
       }
       choice lunch {
           case sports-arena {
               leaf chocolate {
                   type enumeration {
                       enum dark;
                       enum milk;
                       enum first-available;
                   }
               }
           }
       }
    }
}
