module Test {
    yang-version 1;
    namespace http://huawei.com;
    prefix Ant;
    list valid {
        config false;
        key "invalid-interval";
        leaf invalid-interval {
            type "uint16";
            units "seconds";
            status current;
            reference "RFC 6020";
        }
        container valid {
            config true;
            leaf invalid-interval {
                type "uint16";
                units "seconds";
                status current;
                reference "RFC 6020";
            }
        }
    }
}
