module ietf-network {
     yang-version 1;
     namespace "urn:ietf:params:xml:ns:yang:ietf-network";
     prefix nd;

     import ietf-inet-types {
       prefix inet;
     }
       leaf node-ref {
         type node-id;
         description
           "Used to reference a node.
            Nodes are identified relative to the network they are
            contained in.";
       }

    typedef node-id {
       type inet:uri;
       description
         "Identifier for a node.";
     }
   }
