module Test {
    yang-version 1;
    namespace http://huawei.com;
    prefix Ant;
    leaf invalid-interval {
        type hello {
            range "min..4 | 10..max";
        }
    }
    typedef hello {
        type int32 {
            range "1..4 | 10..20";
        }
    }
}
