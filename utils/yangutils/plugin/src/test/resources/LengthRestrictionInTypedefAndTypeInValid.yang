module Test {
    yang-version 1;
    namespace http://huawei.com;
    prefix Ant;
    leaf invalid-interval {
        type hello {
            length "min..20 | 200..max";
        }
    }
    typedef hello {
        type string {
            length "0..100 | 101..200 | 201..300";
        }
    }
}
