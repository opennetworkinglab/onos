module Test {
    yang-version 1;
    namespace http://huawei.com;
    prefix Ant;
    list valid {
        key "ospf";
        unique "ospf isis";
        leaf ospf {
            type "uint16";
            units "seconds";
            status current;
            reference "RFC 6020";
        }
        leaf isis {
            type "uint16";
            units "seconds";
            status current;
            reference "RFC 6020";
        }
    }
}
