submodule test6 {
      
     belongs-to "test5" {
         prefix "test";
    }    

    revision "2016-07-04" {
             description "Initial revision.";
    }
    grouping grouping1 {
        leaf leaf1 {
           type int32;
        }
    }
}
