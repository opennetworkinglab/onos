module Test {
    yang-version 1;
    namespace http://huawei.com;
    prefix Ant;
    list valid {
        key "invalid";
        min-elements 3;
        leaf-list invalid-interval {
            type "uint16";
            units "seconds";
            description "Interval before a route is declared invalid";
        }
        leaf invalid {
            type "uint16";
        }
    }
}
