module Test {
    yang-version 1;
    namespace http://huawei.com;
    prefix Ant;
    leaf invalid-interval {
        type string {
            length "0..100" {
                description "length description";
                reference "length reference";
            }
         }
    }
}
