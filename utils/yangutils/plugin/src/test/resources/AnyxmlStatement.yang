module event {

    namespace "http://example.com/event";
    prefix "ev";

    notification event {
        leaf event-class {
            type string;
        }
        anyxml reporting-entity;
        leaf severity {
            type string;
        }
    }
}
