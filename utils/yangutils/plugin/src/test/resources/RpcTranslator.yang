module Sfc {
    yang-version 1;
    namespace http://huawei.com;
    prefix Ant;
    leaf test{
        type string;
    }
    container my-container{
    leaf my-val{
            type string;
        }
    }
    rpc SFP {
        input {
            leaf port {
                type string;
            }
        }
        output {
            leaf path {
                type string;
            }
        }
    }
}
