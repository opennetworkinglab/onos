module Test {
    yang-version 1;
    namespace http://huawei.com;
    prefix Ant;
    leaf speed {
        type enumeration {
          enum 10m {
	     value -2;
          }
          enum 100m {
	     value "-1";
          }
          enum auto {
	     value 0;
          }
        }
    }
}
