module ietf-network {
    yang-version 1;
    namespace "urn:ietf:params:xml:ns:yang:ietf-network";
    prefix nd;
    container networks {
        description
        "Serves as top-level container for a list of networks.";
        leaf network-id {
            type leafref {
                path "/status/current";
            }
            description
            "Identifies a network.";
        }
    }
    container status {
        leaf current {
            type uint8;
        }
    }
    leaf network-ref {
        type leafref {
            path "/networks/network-id";
        }
    }
}
