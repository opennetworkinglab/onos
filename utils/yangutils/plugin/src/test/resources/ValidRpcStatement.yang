module rock {
    namespace "http://example.net/rock";
    prefix "rock";

    rpc rock-the-house {
        description "description";
        status current;
        reference "reference";
        typedef my-type {
           status deprecated;
           type int32;
        }
        input {
            leaf zip-code {
                type string;
            }
        }
        output {
             leaf status {
                 type string;
             }
        }
    }
}
