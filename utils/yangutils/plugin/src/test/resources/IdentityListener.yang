module IdentityListener{
    yang-version 1;
    namespace http://huawei.com;
    prefix IdentityListener;

    identity tunnel {
        description
           "Base identity from which specific tunnel types are derived.";
    }

    identity tunnel-type {
        description
           "Base identity from which specific tunnel types are derived.";
    }

    identity ref-address-family {
        reference "http://www.iana.org/assignments/address-family-numbers/address-family-numbers.xhtml#address-family-numbers-2";
    }

    identity ipv4-address-family {
        base ref-address-family;
    }

    identity ipv6-address-family {
        base ref-address-family;
    }

    leaf tunnel {
        type identityref {
            base ref-address-family;
        }
    }

    leaf-list network-ref {
        type identityref {
            base ref-address-family;
        }
    }
}
