module Test {
    yang-version 1;
    namespace http://huawei.com;
    prefix Ant;
    list valid {
        config true;
        container container1 {
           leaf leaf1 {
              type "string";
           }
        }
    }
}
