module Test {
    yang-version 1;
    namespace http://huawei.com;
    prefix Ant;
    list valid {
        key "invalid-interval";
        leaf invalid-interval {
            type "uint16";
            units "seconds";
            status current;
            reference "RFC 6020";
        }
        list list1 {
            key "leaf1";
            leaf leaf1 {
                type "uint16";
                units "seconds";
                status current;
                reference "RFC 6020";
            }
        }
    }
}
