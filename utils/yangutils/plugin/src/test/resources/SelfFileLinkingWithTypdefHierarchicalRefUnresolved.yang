module Test {
    yang-version 1;
    namespace http://huawei.com;
    prefix Ant;
    import ietf-yang-types {
             prefix "P";
         }
    typedef Percentage {
    type P:Per;
    }
    container ospf {
        list valid {
            key "invalid-interval";
            leaf invalid-interval {
                type FirstClass;
            }
            typedef FirstClass {
                type PassingClass;
            }
        }
        typedef PassingClass {
            type Percentage;
        }
    }
}
