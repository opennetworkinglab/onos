module Test {
    yang-version 1;
    namespace http://huawei.com;
    prefix Ant;
     leaf mybits {
         type bits {
             bit disable-nagle;
             bit disable-nagle;
             bit Ten-Mb-only;
         }
    }
}
