module Test {
    yang-version 1;
    namespace http://huawei.com;
    prefix Ant;
    leaf invalid-interval {
        type hello {
            pattern "[a-z]";
            pattern "[A-Z]";
            length "min..20 | 201..max";
        }
    }
    typedef hello {
        type string {
            pattern "[0-9]";
            pattern "[\n]";
            length "0..100 | 101..200 | 201..300";
        }
    }
}
