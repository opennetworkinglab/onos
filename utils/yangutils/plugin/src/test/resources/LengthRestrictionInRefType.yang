module Test {
    yang-version 1;
    namespace http://huawei.com;
    prefix Ant;
    leaf invalid-interval {
        type hello {
            length "0..100";
        }
    }
    typedef hello {
        type string;
    }
}
