module test {  
    namespace "xpath:intra:single";  
    prefix test ;  
   
    include test2;

    organization "";  
    contact "";  
       
    description   
        "Defines basic service types for L3VPN service.";  
       
    revision "2015-12-16" {  
        reference "";  
    }  

    augment /cont5/cont6/cont3/cont4 {
       leaf a {
          type int32;
       }
    }
}
