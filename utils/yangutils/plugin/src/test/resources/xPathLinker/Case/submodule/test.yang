module test {  
    namespace "xpath:intra:single";  
    prefix test ;  
   
    include test1;
    include test2;
    include test4;

    organization "";  
    contact "";  
       
    description   
        "Defines basic service types for L3VPN service.";  
       
    revision "2015-12-16" {  
        reference "";  
    }  

    augment /cont5/cont6 {
       leaf a {
          type int32;
       }
    }

   augment /cont3/cont4/cont8 {
       leaf a {
          type int32;
       }
    }
}
