module test2 {  
    namespace "xpath:inter:multi";  
    prefix test2 ;  
      
    organization "";  
    contact "";  
       
    description   
        "Defines basic service types for L3VPN service.";  
       
    revision "2015-12-16" {  
        reference "";  
    }  

   grouping group1 {
    container cont1 {
       leaf leaf1 {
          type int32;
       }
       container cont2 {
          leaf leaf1 {
             type int32;
          }
       }
    }
  }
}
