module test {  
    namespace "xpath:intra:single";  
    prefix test ;  
    
    import test2 {
       prefix test2;
    }
   
    include test1;

    organization "";  
    contact "";  
       
    description   
        "Defines basic service types for L3VPN service.";  
       
    revision "2015-12-16" {  
        reference "";  
    }  

    augment /test2:cont1/test2:cont2/cont2 {
       leaf a {
          type int32;
       }
    }

    augment /cont2/cont3/cont4 {
       leaf a {
          type int32;
       }
    }
}
