submodule test1 {  

    belongs-to test {
         prefix test;
    }           
    
    import test2 {
       prefix test2;
    }
    organization "";  
    contact "";  
       
    description   
        "Defines basic service types for L3VPN service.";  
       
    revision "2015-12-16" {  
        reference "";  
    }  

    augment /test2:cont1/test2:cont2 {
       leaf a {
          type int32;
       }
       container cont2 {
          leaf leaf1 {
             type int32;
          }
       }
    }
}
