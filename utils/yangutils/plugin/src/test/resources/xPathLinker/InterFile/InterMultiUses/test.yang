module test {  
    namespace "xpath:intra:single";  
    prefix test ;  
    
    import test2 {
       prefix test2;
    }
   
    organization "";  
    contact "";  
       
    description   
        "Defines basic service types for L3VPN service.";  
       
    revision "2015-12-16" {  
        reference "";  
    }

    container cont2 {
       leaf a {
          type int32;
       }
       uses test2:group1; 
    }

    augment /cont2/group1/cont1/cont2 {
          leaf a {
          type int32;
       }
    } 
}
