module test {  
    namespace "xpath:intra:single";  
    prefix test ;  
      
    organization "";  
    contact "";  
       
    description   
        "Defines basic service types for L3VPN service.";  
       
    revision "2015-12-16" {  
        reference "";  
    }  

    container cont1 {
       leaf leaf1 {
          type int32;
       }
    }

    augment /cont1 {
       leaf a {
          type int32;
       }

       container cont2 {
           leaf leaf1 {
             type int32;
          }
       }
    }

    augment /cont1/cont2 {
       leaf a {
          type int32;
       }
    }
}
