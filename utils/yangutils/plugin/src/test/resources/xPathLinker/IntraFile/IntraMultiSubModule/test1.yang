submodule test1 {  

    belongs-to "test" {
         prefix "test";
    }           
      
    organization "";  
    contact "";  
       
    description   
        "Defines basic service types for L3VPN service.";  
       
    revision "2015-12-16" {  
        reference "";  
    }  

    container cont2 {
       leaf leaf1 {
          type int32;
       }
       container cont3 {
           leaf leaf3 {
             type int32;
          }
       }
    }
}
