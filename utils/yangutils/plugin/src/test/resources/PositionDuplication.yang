module Test {
    yang-version 1;
    namespace http://huawei.com;
    prefix Ant;
     leaf mybits {
         type bits {
             bit disable-nagle {
                 position 0;
             }
             bit auto-sense-speed {
                 position 1;
             }
             bit Ten-Mb-only {
                 position 1;
             }
         }
    }
}
