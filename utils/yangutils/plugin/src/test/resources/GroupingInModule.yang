module Test {
    yang-version 1;
    namespace http://huawei.com;
    prefix Ant;
    import ietf-yang-types {
             prefix "P";
         }
    grouping endpoint {
        leaf address {
            type P:ip-address;
        }
        leaf port {
            type P:port-number;
        }
    }
}
