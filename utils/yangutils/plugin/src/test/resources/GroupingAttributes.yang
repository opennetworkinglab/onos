module Test {
    yang-version 1;
    namespace http://huawei.com;
    prefix Ant;
    import ietf-yang-types {
             prefix "P";
         }
    list valid {
        key address;
        leaf address {
            type P:ip;
        }
        grouping endpoint {
            description "grouping under test";
            status current;
            reference "RFC 6020";
            leaf address {
                type P:ip-address;
            }
            leaf port {
                type P:port-number;
            }
        }
    }
}
