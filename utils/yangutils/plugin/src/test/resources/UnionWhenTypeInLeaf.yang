module Test {
    yang-version 1;
    namespace http://huawei.com;
    prefix Ant;
    list valid {
        key "invalid-interval";
        leaf invalid-interval {
            type union {
                type int32;
                type enumeration {
                    enum "unbounded";
                }
            }
        }
    }
}
