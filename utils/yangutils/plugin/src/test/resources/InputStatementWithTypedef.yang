module rock {
    namespace "http://example.net/rock";
    prefix "rock";

    rpc activate-software-image {
        description "description";
        input {
            leaf image-name {
                type string;
            }
            typedef my-type {
                status deprecated;
                type int32;
            }
        }
    }
}
