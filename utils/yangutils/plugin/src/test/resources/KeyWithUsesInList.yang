module Test {
    yang-version 1;
    namespace http://huawei.com;
    prefix Ant;
    grouping network {
        leaf invalid-interval {
            type "string";
            units "seconds";
            status current;
            reference "RFC 6020";
        }
    }
    list valid {
        key "invalid-interval";
        leaf invalid {
            type "string";
            units "seconds";
            status current;
            reference "RFC 6020";
        }
        uses "network";
    }
}
