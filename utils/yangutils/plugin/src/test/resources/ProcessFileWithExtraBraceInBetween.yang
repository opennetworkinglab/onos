module Test {
    yang-version 1;
    namespace http://huawei.com;
    prefix Ant;
    import ietf-yang-types {
        prefix "P";
    }
    grouping Percentage {
        leaf hello{
            type string;
        }
        leaf invalid1{
            type string;
        }
        }
        leaf invalid2{
            type string;
        }
    }
    container ospf {
        list valid {
            key "invalid";
            leaf invalid{
                type string;
            }
            uses Ant:FirstClass;
            grouping FirstClass {
                uses P:PassingClass;
            }
        }
        grouping PassingClass {
            uses Ant:Percentage;
        }
    }
}
