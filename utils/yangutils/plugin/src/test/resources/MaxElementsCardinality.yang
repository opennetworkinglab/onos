module Test {
    yang-version 1;
    namespace http://huawei.com;
    prefix Ant;
    leaf-list invalid-interval {
        type "uint16";
        units "seconds";
        max-elements 4;
        max-elements 6;
        description "Interval before a route is declared invalid";
        config true;
        status current;
        reference "RFC 6020";
    }
}
