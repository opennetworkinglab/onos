module Test {
    yang-version 1;
    namespace http://huawei.com;
    prefix Ant;
     container food1 {
       choice snack;
       choice lunch;
    }
     container food2 {
       choice snack;
       choice lunch;
    }
}
