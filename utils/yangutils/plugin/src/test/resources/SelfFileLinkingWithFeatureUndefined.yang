module syslog {
    yang-version 1;
    namespace http://huawei.com;
    prefix "sys";

    container speed {
        leaf local-storage-limit {
            if-feature local-storage;
            type uint64;
            units "kilobyte";
            config false;
            description
                 "The amount of local storage that can be
                  used to hold syslog messages.";
        }
    }
}
