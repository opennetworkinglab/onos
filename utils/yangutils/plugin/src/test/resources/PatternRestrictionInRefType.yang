module Test {
    yang-version 1;
    namespace http://huawei.com;
    prefix Ant;
    leaf invalid-interval {
        type hello {
            pattern "[a-zA-Z]";
        }
    }
    typedef hello {
        type string;
    }
}
