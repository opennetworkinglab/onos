module Test {
    yang-version 1;
    namespace http://huawei.com;
    prefix Ant;
    leaf-list invalid-interval {
        type string {
            length "0..18446744073709551617";
         }
    }
}
