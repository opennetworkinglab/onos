module Test {
    yang-version 1;
    namespace http://huawei.com;
    prefix Ant;

    typedef topInt {
       type int64;
       default "10";
    }

    typedef midInt {
       type topInt;
    }

    leaf lowInt {
        type midInt;
    }
}
