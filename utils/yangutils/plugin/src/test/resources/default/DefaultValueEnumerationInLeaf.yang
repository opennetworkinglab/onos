module Test {
    yang-version 1;
    namespace http://huawei.com;
    prefix Ant;

     leaf myenum {
         type enumeration {
             enum zero;
             enum one;
             enum seven {
                 value 7;
             }
         }
         default "one";
     }
}
