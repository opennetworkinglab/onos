module Test {
    yang-version 1;
    namespace http://huawei.com;
    prefix Ant;
    leaf invalid-interval {
        type "uint16";
        units "seconds";
        default "x";
        description "Interval before a route is declared invalid";
        config true;
        mandatory true;
        status current;
        reference "RFC 6020";
    }
}
