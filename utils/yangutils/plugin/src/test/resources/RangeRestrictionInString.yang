module Test {
    yang-version 1;
    namespace http://huawei.com;
    prefix Ant;
    leaf invalid-interval {
        type hello;
    }
    typedef hello {
        type string {
            range "1..4 | 10..20";
        }
    }
}
