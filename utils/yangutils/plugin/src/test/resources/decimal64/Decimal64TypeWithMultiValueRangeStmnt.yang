module Test {
    yang-version 1;
    namespace http://huawei.com;
    prefix Ant;
    leaf validDecimal {
         type decimal64 {
            fraction-digits 18; 
            range "-9.22..7.22 | 8 | 9..max";
         }
    }
}
