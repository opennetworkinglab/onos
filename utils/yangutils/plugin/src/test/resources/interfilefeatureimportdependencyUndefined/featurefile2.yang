module syslog2 {
     yang-version 1;
     namespace "http://huawei2.com";
     prefix "sys2";

     import "syslog3" {
        prefix "sys3";
     }

     feature p2mp-te {
       description "Indicates support for P2MP-TE";
       if-feature "sys3:extended-admin-groups";
     }
}
