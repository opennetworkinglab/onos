module Test {
    yang-version 1;
    namespace http://huawei.com;
    prefix Ant;
    leaf invalid-interval {
        units "seconds";
        type "uint16";
        description "Interval before a route is declared invalid";
        config true;
        mandatory true;
        status current;
        reference "RFC 6020";
    }
}
