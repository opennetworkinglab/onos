module Test {
    yang-version 1;
    namespace http://huawei.com;
    prefix Ant;
    grouping currentcheck {
        leaf invalid-interval {
            type identityref {
            }
        }
    }
}
