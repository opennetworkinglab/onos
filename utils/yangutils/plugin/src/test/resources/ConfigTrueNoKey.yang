module Test {
    yang-version 1;
    namespace http://huawei.com;
    prefix Ant;
    list valid {
        config true;
        leaf invalid-interval {
            type "string";
            units "seconds";
            status current;
            reference "RFC 6020";
        }
    }
}
