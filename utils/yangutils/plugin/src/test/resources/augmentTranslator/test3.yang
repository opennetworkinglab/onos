module test2 {  
    namespace "test2:test2";  
    prefix test2 ;  
                  
    import test1{  
       prefix test1;
    }  
    organization "";  
    contact "";  
       
    description   
       "Defines basic service types for L3VPN service.";  
       
    revision "2015-12-16" {  
       reference "";  
    }  


    augment /test1:cont1/test1:cont2/test1:cont1s/test1:cont1s {
        leaf leaf5 {
          type int32;
        }
        container aa {
        }
    }
}
