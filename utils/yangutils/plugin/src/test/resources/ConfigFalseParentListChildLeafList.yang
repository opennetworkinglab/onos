module Test {
    yang-version 1;
    namespace http://huawei.com;
    prefix Ant;
    list valid {
        key "invalid-interval";
        config false;
        leaf-list invalid-interval {
            type "uint16";
            config true;
            units "seconds";
            status current;
            reference "RFC 6020";
        }
    }
}
