module Test {
    yang-version 1;
    namespace http://huawei.com;
    prefix Ant;
    grouping endpoint {
        leaf address {
            type ip-address;
        }
    leaf port {
        type port-number;
        }
    }
    container valid {
        grouping endpoint {
            leaf address {
                type ip-address;
            }
            leaf port {
                type port-number;
            }
        }
    }
}
