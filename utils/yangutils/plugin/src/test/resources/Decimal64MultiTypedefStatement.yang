module Test {
    yang-version 1;
    namespace http://huawei.com;
    prefix Ant;

    typedef topDecimal {
         type decimal64 {
            fraction-digits 4; 
         }
    }

    typedef validDecimal {
         type topDecimal;
    }

    leaf setFourDecimal {
         type validDecimal;
    } 
}
