module syslog1 {
     yang-version 1;
     namespace "http://huawei3.com";
     prefix "sys1";

     include "syslog2";

     feature frr-te {
       description "Indicates support for TE FastReroute (FRR)";
       if-feature "p2mp-te";
     }

     container speed {
         leaf local-storage-limit {
             if-feature frr-te;
             type uint64;
             units "kilobyte";
             config false;
             description
                     "The amount of local storage that can be
                      used to hold syslog messages.";
         }
     }
}
