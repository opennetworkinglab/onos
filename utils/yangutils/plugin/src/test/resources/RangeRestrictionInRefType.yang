module Test {
    yang-version 1;
    namespace http://huawei.com;
    prefix Ant;
    leaf invalid-interval {
        type hello {
            range "1..4 | 10..20";
        }
    }
    typedef hello {
        type int32;
    }
}
