module Test {
    yang-version 1;
    namespace http://huawei.com;
    prefix Ant;
    typedef Percentage {
    type int32;
    }
    container ospf {
        list valid {
            key "invalid-interval";
            leaf invalid-interval {
                type Ant:FirstClass;
            }
            typedef FirstClass {
                type PassingClass;
            }
        }
        typedef PassingClass {
            type Ant:Percentage;
        }
    }
}
