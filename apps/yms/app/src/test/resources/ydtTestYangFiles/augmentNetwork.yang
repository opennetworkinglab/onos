module augmentNetwork {

    yang-version 1;

    namespace "ydt.augmentNetwork";

    prefix "aug";

    import yms-ietf-network {
        prefix nd;
    }


    organization "ON-LAB";

    description "This module defines for augmentNetwork classifier.";

    revision "2016-05-24" {
        description "Initial revision.";
    }

    augment "/nd:networks/nd:network" {
        description
        "Add container to the network model.";
        container cont1s {
            container cont1s {
                leaf fine {
                    type string;
                }
            }
        }
    }
}
