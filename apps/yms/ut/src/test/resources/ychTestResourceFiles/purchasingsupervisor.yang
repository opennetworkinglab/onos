module ych-purchasingsupervisor {

    yang-version 1;

    namespace "ych.purchasing-supervisor";

    prefix "purchasing";

    organization "ON-LAB";

    description "This module defines for purchasing-supervisor.";

    revision "2016-05-24" {
        description "Initial revision.";
    }

    container ych-purchasing-supervisor {
        leaf ych-purchasing-specialist {
            type string;
            description "name of the purchasing-specialist person";
        }

        leaf ych-purchasing-support {
            type string;
            description "name of the support person";
        }

        leaf ych-purchasing-options {
            type bits {
                bit "option0";
                bit "option1";
                bit "option2";
                bit "option3";
            }
            description
            "A bit mask that may have 0, 1, many or all options present";
        }

        container ych-is-manager {
            presence "If node is present denotes that supervisor is a manager";
        }
    }
}
