module enumtest {

    yang-version 1;

    namespace "ydt.enumtest";

    prefix "enumtest";

    organization "ON-LAB";

    description "This module defines for enumtest classifier.";

    revision "2016-05-24" {
        description "Initial revision.";
    }

    list enumList {
        key enumleaf;
        leaf enumleaf {
            type enumeration {
              enum ten { value "10";}
              enum hundred { value "100";}
              enum thousand { value "1000"; }
            }
        }
    }
}
