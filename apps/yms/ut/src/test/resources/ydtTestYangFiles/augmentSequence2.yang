module augmentSequence2 {

    yang-version 1;

    namespace "ydt.augmentSequence2";

    prefix "sequence2";

    import augmentSequence {
        prefix aug;
    }

    organization "ON-LAB";

    description "This module defines for augmentSequence2 classifier.";

    revision "2016-05-24" {
        description "Initial revision.";
    }

    augment "/aug:l1" {
        container c2 {
            leaf leaf2 {
                  type int8;
            }
        }
    }
}
